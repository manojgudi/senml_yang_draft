module lora-sensor-senml {
    yang-version 1.1;
    namespace "urn:ietf:params:xml:ns:yang:lora-sensor";
    prefix "lss";

    import senml {
        prefix lss-senml;
    }

    import ietf-lora {
        prefix lss-ietf-lora;
    }

    list e {
        key t;
        uses lss-senml:senml-grouping {
            refine bver {
                default 11;
            }
        }
    }

    container lora {
        uses lss-ietf-lora:mode;
    }
}
